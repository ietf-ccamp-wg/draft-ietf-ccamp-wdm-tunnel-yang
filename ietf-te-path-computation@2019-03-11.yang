module ietf-te-path-computation {
  yang-version 1.1;
  namespace "urn:ietf:params:xml:ns:yang:ietf-te-path-computation";
  // replace with IANA namespace when assigned

  prefix "tepc";

  import ietf-inet-types {
    prefix "inet";
  }

  import ietf-te {
    prefix "te";
    revision-date "2019-02-15";
    reference 
    "I-D.ietf-teas-yang-te-19: A YANG Data Model for Traffic
     Engineering Tunnels and Interfaces. ";
  }

  import ietf-te-types {
    prefix te-types;
    revision-date "2019-02-06";
    reference "draft-ietf-teas-yang-te-types: A YANG Data Model for
               Common Traffic Engineering Types";
  }

  organization
    "Traffic Engineering Architecture and Signaling (TEAS)
     Working Group";

  contact
    "WG Web:   <http://tools.ietf.org/wg/teas/>
     WG List:  <mailto:teas@ietf.org>

     WG Chair: Lou Berger
               <mailto:lberger@labn.net>

     WG Chair: Vishnu Pavan Beeram
               <mailto:vbeeram@juniper.net>

   ";

  description "YANG model for stateless TE path computation";

  revision "2019-03-11" {
    description
      "Initial revision";
    reference
      "draft-ietf-teas-yang-path-computation";
  }

  /*
   * Features
   */

  feature stateless-path-computation {
    description
      "This feature indicates that the system supports
       stateless path computation.";
  }

  /*
   * Groupings
   */

  grouping path-info {
    uses te-types:generic-path-properties;
    description "Path computation output information";
  }

  grouping requested-info {
    description
      "This grouping defines the information (e.g., metrics)
       which must be returned in the response";
    list requested-metrics {
      key 'metric-type';
      description
        "The list of the requested metrics
         The metrics listed here must be returned in the response.
         Returning other metrics in the response is optional.";
      leaf metric-type {
        type identityref {
          base te-types:path-metric-type;
        }
        description
          "The metric that must be returned in the response";
      }
    }
    leaf return-srlgs {
      type boolean;
      default false;
      description
        "If true, path srlgs must be returned in the response.
         If false, returning path srlgs in the response optional.";
    }
    leaf return-affinities {
      type boolean;
      default false;
      description
      "If true, path affinities must be returned in the response.
       If false, returning path affinities in the response is
       optional.";
    }
  }

  grouping requested-state {
    description
      "Configuration for the transient state used
       to report the computed path";
    leaf timer {
      type uint16;
      units minutes;
      default 10;
      description
        "The timeout after which the transient state reporting
         the computed path should be removed.";
    }
    leaf transaction-id {
      type string;
      description
        "
         The transaction-id associated with this path computation
         to be used for fast deletion of the transient states
         associated with multiple path computations.

         This transaction-id can be used to explicitly delete all
         the transient states of all the computed paths associated
         with the same transaction-id.

         When one path associated with a transaction-id is setup,
         the transient states of all the other computed paths
         with the same transaction-id are automatically removed.

         If not specified, the transient state is removed only
         when the timer expires (when the timer is specified)
         or not created at all (stateless path computation,
         when the timer is not specified).
        ";
    }
    leaf tunnel-name {
      type string;
      description
        "
         The suggested name to be assigned to the te-tunnel
         instance which is created to report the computed path.

         In case multiple paths are requested with the same
         suggested name, the server will create only one te-tunnel
         instance to report all the computed paths
         with the same suggested name.

         A different name can be assigned by server (e.g., when a
         te-tunnel with this name already exists).
        ";
    }
    choice path {
      description
        "The transient state of the computed path can be reported
         as a primary or a secondary path of a te-tunnel";
      case primary {
        leaf primary-path-name {
          type string;
          description
            "
             The suggested name to be assigned to the
             p2p-primary-path instance which is created
             to report the computed path.

             A different name can be assigned by the server
             (e.g., when a p2p-primary-path with this name
             already exists).
            ";
        }
      }
      case secondary {
        leaf secondary-path-name {
          type string;
          description
            "
             The suggested name to be assigned to the
             p2p-secondary-path instance which is created
             to report the computed path.

             A different name can be assigned by the server
             (e.g., when a p2p-secondary-path with this
             name already exists).

             If not specified, the a p2p-primary-path is created
             by the server.
            ";
        }
      }
    }
  }
  grouping reported-state {
    description
      "Information about the transient state created
       to report the computed path";

    leaf tunnel-ref {
      type te:tunnel-ref;
      description
        "
         Reference to the tunnel that reports the transient state
         of the computed path.

         If no transient state is created, this attribute is empty.
        ";
    }
    choice path {
      description
        "The transient state of the computed path can be reported
         as a primary or a secondary path of a te-tunnel";
      case primary {
        leaf primary-path-ref {
          type leafref {
            path "/te:te/te:tunnels/" +
                 "te:tunnel[te:name=current()/../tunnel-ref]/" +
                 "te:p2p-primary-paths/te:p2p-primary-path/" +
                 "te:name";
          }
          must "../tunnel-ref" {
            description
              "The primary-path-name can only be reported
               if also the tunnel is reported
               to provide the complete reference.";
          }
          description
            "
             Reference to the p2p-primary-path that reports
             the transient state of the computed path.

             If no transient state is created,
             this attribute is empty.
            ";
        }
      }
      case secondary {
        leaf secondary-path-ref {
          type leafref {
            path "/te:te/te:tunnels/" +
                 "te:tunnel[te:name=current()/../tunnel-ref]/" +
                 "te:p2p-secondary-paths/te:p2p-secondary-path/" +
                 "te:name";
          }
          must "../tunnel-ref" {
            description
              "The secondary-path-name can only be reported
               if also the tunnel is reported to provide
               the complete reference.";
          }
          description
            "
             Reference to the p2p-secondary-path that reports
             the transient state of the computed path.

             If no transient state is created,
             this attribute is empty.
            ";
        }
      }
    }
  }

  identity svec-metric-type {
    description
      "Base identity for svec metric type";
  }

  identity svec-metric-cumul-te {
    base svec-metric-type;
    description
      "TE cumulative path metric";
  }

  identity svec-metric-cumul-igp {
    base svec-metric-type;
    description
      "IGP cumulative path metric";
  }

  identity svec-metric-cumul-hop {
    base svec-metric-type;
    description
      "Hop cumulative path metric";
  }

  identity svec-metric-aggregate-bandwidth-consumption {
    base svec-metric-type;
    description
      "Cumulative bandwith consumption of the set of
       synchronized paths";
  }

  identity svec-metric-load-of-the-most-loaded-link {
    base svec-metric-type;
    description
      "Load of the most loaded link";
  }

  grouping svec-metrics-bounds_config {
    description
      "TE path metric bounds grouping for computing a set of
       synchronized requests";
    leaf metric-type {
      type identityref {
        base svec-metric-type;
      }
      description "TE path metric type usable for computing a set of
         synchronized requests";
    }
    leaf upper-bound {
      type uint64;
      description "Upper bound on end-to-end svec path metric";
    }
  }

  grouping svec-metrics-optimization_config {
    description
      "TE path metric bounds grouping for computing a set of
       synchronized requests";

    leaf metric-type {
      type identityref {
        base svec-metric-type;
      }
      description "TE path metric type usable for computing a set of
         synchronized requests";
    }
    leaf weight {
      type uint8;
      description "Metric normalization weight";
    }
  }

  grouping svec-exclude {
    description "List of resources to be excluded by all the paths
      in the SVEC";
    container exclude-objects {
      description "resources to be excluded";
      list excludes {
        key index;
        ordered-by user;
        leaf index {
           type uint32;
           description "XRO subobject index";
        }
        description
          "List of explicit route objects to always exclude
           from synchronized path computation";
        uses te-types:explicit-route-hop;
      }
    }
  }

  grouping synchronization-constraints {
    description "Global constraints applicable to synchronized
      path computation";
    container svec-constraints {
      description "global svec constraints";
      list path-metric-bound {
        key metric-type;
        description "list of bound metrics";
        uses svec-metrics-bounds_config;
      }
    }
    uses te-types:generic-path-srlgs;
    uses svec-exclude;
  }

  grouping synchronization-optimization {
      description "Synchronized request optimization";
    container optimizations {
      description
        "The objective function container that includes attributes
         to impose when computing a synchronized set of paths";

      choice algorithm {
        description "Optimizations algorithm.";
        case metric {
          if-feature te-types:path-optimization-metric;
          list optimization-metric {
            key "metric-type";
            description "svec path metric type";
            uses svec-metrics-optimization_config;
          }
        }
        case objective-function {
          if-feature te-types:path-optimization-objective-function;
          container objective-function {
            description
              "The objective function container that includes
               attributes to impose when computing a TE path";
            leaf objective-function-type {
              type identityref {
                base te-types:objective-function-type;
              }
              default te-types:of-minimize-cost-path;
              description "Objective function entry";
            }
          }
        }
      }
    }
  }

  grouping synchronization-info {
    description "Information for sync";
    list synchronization {
      key "synchronization-id";
      description "sync list";
      leaf synchronization-id {
        type uint32;
        description "index";
      }
      container svec {
        description
         "Synchronization VECtor";
        leaf relaxable {
          type boolean;
          default true;
          description
           "If this leaf is true, path computation process is
            free to ignore svec content.
            Otherwise, it must take into account this svec.";
        }
        uses te-types:generic-path-disjointness;
        leaf-list request-id-number {
          type uint32;
          description
            "This list reports the set of path computation
             requests that must be synchronized.";
        }
      }
      uses synchronization-constraints;
      uses synchronization-optimization;
    }
  }

  grouping no-path-info {
    description "no-path-info";
    container no-path {
      presence "Response without path information, due to failure
        performing the path computation";
      description "if path computation cannot identify a path,
        rpc returns no path.";
    }
  }

  /*
   * These groupings should be removed when defined in te-types
   */

  grouping encoding-and-switching-type {
    description
      "Common grouping to define the LSP encoding and
       switching types";

    leaf encoding {
      type identityref {
        base te-types:lsp-encoding-types;
      }
      description "LSP encoding type";
      reference "RFC3945";
    }
    leaf switching-type {
      type identityref {
        base te-types:switching-capabilities;
      }
      description "LSP switching type";
      reference "RFC3945";
    }
  }

  grouping tunnel-p2p-common-params {
    description
      "Common grouping to define the TE tunnel parameters";

    uses encoding-and-switching-type;
    leaf source {
      type inet:ip-address;
      description "TE tunnel source address.";
    }
    leaf destination {
      type inet:ip-address;
      description "P2P tunnel destination address";
    }
    leaf src-tp-id {
      type binary;
      description
        "TE tunnel source termination point identifier.";
    }
    leaf dst-tp-id {
      type binary;
      description
        "TE tunnel destination termination point identifier.";
    }
    leaf bidirectional {
      type boolean;
      default 'false';
      description "TE tunnel bidirectional";
    }
  }

  /*
   * AUGMENTS TO TE RPC
   */

  augment "/te:tunnels-rpc/te:input/te:tunnel-info" {
    description "Path Computation RPC input";
    list path-request {
      key "request-id";
      description "request-list";
      leaf request-id {
        type uint32;
        mandatory true;
        description
          "Each path computation request is uniquely identified
           by the request-id-number.";
      }
      uses tunnel-p2p-common-params;
      uses te-types:te-topology-identifier;
      uses te-types:path-constraints-route-objects;
      uses te-types:generic-path-constraints;
      uses te-types:generic-path-optimization;
      uses te:path-access-segment-info;
      uses requested-info;
      container requested-state {
        presence
          "Request temporary reporting of the computed path state";
        description
          "Configures attributes for the temporary reporting of the
           computed path state (e.g., expiration timer).";
        uses requested-state;
      }
    }
    uses synchronization-info;
  }

  augment "/te:tunnels-rpc/te:output/te:result" {
    description "Path Computation RPC output";
    list response {
      key "response-id";
      config false;
      description "response";
      leaf response-id {
        type uint32;
        description
          "The response-id has the same value of the corresponding
           request-id.";
      }
      choice response-type {
        config false;
        description "response-type";
        case no-path-case {
          uses no-path-info;
        }
        case path-case {
          container computed-path {
            uses path-info;
            uses reported-state;
            description "Path computation service.";
          }
        }
      }
    }
  }

  augment "/te:tunnels-rpc/te:input/te:tunnel-info" {
    description "Path Delete RPC input";
    leaf-list deleted-paths-transaction-id {
      type string;
      description
        "The list of the transaction-id values of the
         transient states to be deleted";
    }
  }

  augment "/te:tunnels-rpc/te:output/te:result" {
    description "Path Delete RPC output";
    leaf-list deleted-paths-transaction-id {
      type string;
      description
        "The list of the transaction-id values of the
         transient states that have been successfully deleted";
    }
  }
}
